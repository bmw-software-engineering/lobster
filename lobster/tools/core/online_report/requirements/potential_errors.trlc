package UseCases
import req

req.PotentialError Incorrect_GitHub_Reference_in_Output {
    summary = "LOBSTER online report writes incorrect GitHub reference for an item"
    description = '''
      The GitHub URL, commit SHA, or line number for an item in the output file is incorrect or missing.
    '''
    impacts = [
      '''If the GitHub reference is wrong or missing, the requirements manager cannot reliably map items to their source code location, commit, or line, which can lead to traceability gaps and incorrect audits.'''
    ]
    affects = [Item_GitHub_Source]
    impact_type = req.Impact_Type.Safety
}

req.PotentialError Online_Report_Extract_Wrong_Item_Data_in_Output{
    summary = "LOBSTER online report writes wrong item data into the output file"
    description = '''
      The data of the items in the output file is not equal to the data of the items in the input file.
      '''
    impacts = [
      '''If item identifiers are wrong, the quality manager could justify that a certain item
         does not need a trace to another item, but in reality a different item violates the tracing policy.
         The quality manager might release a software product which should not be released. If other item data is wrong, the same can happen.'''
    ]

    affects = [Item_GitHub_Source]
    impact_type = req.Impact_Type.Safety
}

req.PotentialError Output_Despite_Missing_Config_File_Online_Report {
		summary = "Output generated without configuration file"
		description = '''
			The user does not provide a valid path to a configuration file,
			but the lobster-online_report tool generates valid output nevertheless, potentially based on
			irrelevant report file.
			For example, the lobster-online tool might consider the current working directory
			as source of report file, and these do in fact contain links to real requirements,
			such that lobster-online_report would compute a non-zero coverage value.
		'''
		impacts = [
			'''If the lobster-online_report tool generates a valid output file, then the invalid input path could
				remain undetected, and subsequent tools of the LOBSTER tool chain
				could consume unqualified input data.''',
		]

		affects = [Item_GitHub_Source]
		impact_type = req.Impact_Type.Safety
}

req.PotentialError Output_Despite_Config_File_Error_Online_Report {
		summary = "Output generated with an invalid configuration file"
		description = '''
			The user provides an invalid configuration file, but the lobster-online_report tool
			generates valid output nevertheless, potentially based on
			irrelevant report file.
			This includes cases where the config file:
			- contains invalid data,
			- is missing required keys or attributes,
		'''
		impacts = [
			'''If the lobster-online_report tool generates a valid output file, then the invalid configuration file could
				remain undetected, and subsequent tools of the LOBSTER tool chain
				could consume unqualified input data.''',
		]

		affects = [Item_GitHub_Source]
		impact_type = req.Impact_Type.Safety
}

package core_report_req
import req

req.Software_Requirement Policy_Builder_Rejects_Duplicate_Level_Names {
  description = '''
    IF a raw tracing policy contains two or more levels declared with the same name,
    THEN the "build_tracing_policy" function SHALL raise a fatal LOBSTER_Error
    with the message "duplicate declaration" at the location of the repeated declaration.
  '''
}

req.Software_Requirement Policy_Builder_Rejects_Missing_Source_File {
  description = '''
    IF a level's source file entry names a file that does not exist on disk,
    THEN the "build_tracing_policy" function SHALL raise a fatal LOBSTER_Error
    with the message "cannot find file <path>", where <path> is the file path
    given in the source entry.
  '''
  derived_from = [Missing_Required_Files_Error]
}

req.Software_Requirement Policy_Builder_Rejects_Self_Trace {
  description = '''
    IF a level's "trace to" list contains the level's own name,
    THEN the "build_tracing_policy" function SHALL raise a fatal LOBSTER_Error
    with the message "cannot trace to yourself".
  '''
}

req.Software_Requirement Policy_Builder_Rejects_Unknown_Trace_To_Target {
  description = '''
    IF a level's "trace to" list references a level name that is not declared
    anywhere in the raw tracing policy,
    THEN the "build_tracing_policy" function SHALL raise a fatal LOBSTER_Error
    with the message "unknown item <target>", where <target> is the undeclared
    level name.
  '''
  derived_from = [Invalid_Trace_To]
}

req.Software_Requirement Policy_Builder_Rejects_Unknown_Requires_Level {
  description = '''
    IF a level's "requires" entry names a candidate level that is not declared
    anywhere in the raw tracing policy,
    THEN the "build_tracing_policy" function SHALL raise a fatal LOBSTER_Error
    with the message "unknown level <name>", where <name> is the undeclared
    level name.
  '''
}

req.Software_Requirement Policy_Builder_Rejects_Untraced_Requires {
  description = '''
    IF a level's "requires" entry names a candidate level that does not have
    a "trace to" entry pointing at the requiring level,
    THEN the "build_tracing_policy" function SHALL raise a fatal LOBSTER_Error
    with the message "<candidate> cannot trace to <level> items".
  '''
}

req.Software_Requirement Policy_Builder_Derives_Breakdown_Requirements {
  description = '''
    IF a level does not declare any "requires" entry,
    THEN the "build_tracing_policy" function SHALL derive its
    "breakdown_requirements" as one single-candidate OR-group per other level
    that declares a "trace to" entry pointing at it.
    OTHERWISE, the function SHALL translate each declared "requires" entry
    into one OR-group containing the candidate levels named in that entry, in
    their declared order.
  '''
}

req.Software_Requirement Policy_Builder_Derives_Tracing_Direction_Flags {
  description = '''
    FOR each valid "trace to" entry from a level to another level, the
    "build_tracing_policy" function SHALL append the target name to the declaring
    level's "traces" list, set "needs_tracing_up" to true on the declaring level,
    AND set "needs_tracing_down" to true on the targeted level.
  '''
}

req.Software_Requirement Policy_Builder_Preserves_Level_Declaration_Order {
  description = '''
    IF a raw tracing policy contains uniquely named levels,
    THEN the "build_tracing_policy" function SHALL return one level definition
    for each raw level, in the same order as the raw levels, with each definition
    retaining the raw level's name and kind.
  '''
}

req.Software_Requirement Policy_Loader_Reads_Yaml_Policy_By_Extension {
  description = '''
    IF the file name given to the "load_tracing_policy" function has the
    extension ".yaml" or ".yml" (compared case-insensitively),
    THEN the function SHALL read the file with the YAML policy reader,
    AND SHALL NOT use the legacy parser,
    AND SHALL NOT print a deprecation warning,
    AND SHALL return the level definitions built from the raw policy.
  '''
  derived_from = [Coverage_Computed_From_Yaml_Tracing_Policy]
}

req.Software_Requirement Policy_Loader_Warns_On_Legacy_Policy {
  description = '''
    IF the file name given to the "load_tracing_policy" function does not have
    the extension ".yaml" or ".yml",
    THEN the function SHALL print a warning to standard output that names the file
    and states that the tracing-policy in the LOBSTER configuration language is
    deprecated,
    AND SHALL parse the file with the legacy parser,
    AND SHALL return the level definitions built from the raw policy.
  '''
  derived_from = [Legacy_Tracing_Policy_Deprecation_Warning]
}

req.Software_Requirement Yaml_Policy_Reader_Reads_Levels {
  description = '''
    IF the file given to the "read_yaml_policy" function is a valid YAML tracing
    policy,
    THEN the function SHALL return a raw policy with one raw level per entry of
    the "levels" list, in the same order,
    AND each raw level SHALL retain its name, kind, "source" entries,
    "trace-to" entries and "requires" OR-groups, with omitted optional entries
    being empty,
    AND every location stored in the raw policy SHALL be the policy file.
  '''
  derived_from = [Coverage_Computed_From_Yaml_Tracing_Policy]
}

req.Software_Requirement Yaml_Policy_Reader_Reports_Invalid_Policy_With_Line {
  description = '''
    IF the file given to the "read_yaml_policy" function is not valid YAML
    or violates the tracing policy schema,
    THEN the function SHALL raise a LOBSTER_Exception
    whose message states "invalid tracing policy"
    AND begins, for each reported problem, with "<file>:<line>:", where <line> is
    the 1-based line of the offending element in the file
    (or of the nearest enclosing element if the offending element is missing).
  '''
}

req.Software_Requirement Yaml_Validation_Validates_File_Against_Schema {
  description = '''
    The "validate_yaml_file" function SHALL load the given schema file and read the
    given YAML file as UTF-8, independent of the platform's default encoding,
    AND SHALL validate the file content against the loaded schema,
    AND SHALL report the absolute path of the YAML file in validation errors,
    AND SHALL let validation errors propagate to the caller.
  '''
  derived_from = [Coverage_Computed_From_Yaml_Tracing_Policy]
}

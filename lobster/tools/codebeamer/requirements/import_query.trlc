package codebeamer_req
import req
import UseCases

req.System_Requirement Query_Id_Parameter {
  description = '''
    IF an element given through the yaml config file option "import_query" is a valid codebeamer query id
    (integer greater than zero),
    THEN the tool shall request items from the codebeamer server with the given query id
    according to [[Paginated_Query_Extraction_Correctness]]
    AND write the obtained codebeamer items in the LOBSTER interchange format to the file given in the "out" parameter
  '''
  derived_from = [
    UseCases.List_Ok_Items,
    UseCases.List_Not_Ok_Items,
    UseCases.Item_Coverage
  ]
}

req.System_Requirement Query_String_Parameter {
  description = '''
    IF an element given through the yaml config file option "import_query" is valid
    codebeamer query string,
    THEN the tool shall request items from the codebeamer server with the given query
    string according to [[Paginated_Query_Extraction_Correctness]]
    AND write the obtained codebeamer items in the LOBSTER interchange format to the file
    given in the "out" parameter.
  '''
  derived_from = [
    UseCases.List_Ok_Items,
    UseCases.List_Not_Ok_Items,
    UseCases.Item_Coverage
  ]
}

req.System_Requirement Invalid_Import_Query_String_Format {
  description = '''
    IF the yaml config file option "import_query" is a string that starts with "-",
    THEN the tool shall print an error message to STDERR
    ("import_query must be a positive integer" IF the remaining characters are all
    digits, OTHERWISE "import_query must be a valid cbQL query")
    AND shall exit with a non-zero return code.

    Note: A cbQL query cannot start with a hyphen ("-").
  '''
  derived_from = [
    UseCases.List_Ok_Items,
    UseCases.List_Not_Ok_Items,
    UseCases.Item_Coverage,
  ]
}

req.System_Requirement Numeric_Import_Query_String_Treated_As_Id {
  description = '''
    IF the yaml config file option "import_query" is a string containing only digits,
    THEN the tool shall convert it to an integer
    AND treat it identically to specifying that integer directly as a query id.
  '''
  derived_from = [
    UseCases.Tool_Usability,
  ]
}

package system_test
import req

// These requirements describe what the system test runner must be able to do.

req.System_Requirement Test_Run {
    description = '''
        The test framework shall create a new temporary directory for each test case,
        AND copy the necessary test input files into that folder
        AND set the current working directory to that directory
        AND use the "coverage" tool to measure the branch coverage
        AND then execute the tool under test.

        Notes:
        - The measurable result of this requirement is a "coverage" file and
          the test result (success or failure).
        - In theory the branch coverage shall only be measured for requirement-based
          tests, but for the time being we don't implement such a logic.
          Instead, we aim to write requirements for all tests. If we come across
          a situation where that is not possible, then we rethink our decision.
    '''
}

req.System_Requirement Fail_on_Cmd_Output_Mismatch {
    description = '''
        A system test case shall fail, if the actual command line output of the tool
        under test does not match the expected command line output.
    '''
}

req.System_Requirement Fail_on_Exit_Code_Mismatch {
    description = '''
        A system test case shall fail, if the actual exit code of the tool
        under test does not match the expected exit code.
    '''
}

req.System_Requirement Fail_on_Output_File_Mismatch {
    description = '''
        A system test case shall fail, if the content of the LOBSTER output files
        which were generated by the tool under test
        does not match the content of the corresponding expectation files.

        The paths in the expectation files
        - may contain the placeholder "CURRENT_WORKING_DIRECTORY",
        - and are stored in POSIX format (using forward slashes).

        The test framework shall compare paths regardless of the path format (e.g. POSIX/Windows).

        Reason: lobster tools use the path format of the operating system they are running on.
    '''
}

req.Software_Requirement Provide_Virtual_Environment {
    description = '''
        The test runner shall run tests of "lobster-html-report" inside a virtual environment
        where "graphviz" is available according to the needs of the test.
    '''
}

req.Software_Requirement Enrich_With_Hash {
    description = '''
        The test asserter shall provide a function to enrich the LOBSTER file, which
        represents the expectation value, with the git hash of the current commit hash
        of the underlying git repository.
    '''
}

req.Software_Requirement Create_Temporary_Directory {
    description = '''
        The system test case class shall provide a function to create a new temporary directory.
    '''
    derived_from = [Test_Run]
}

req.Software_Requirement Delete_Temporary_Directory {
    description = '''
        The system test case class delete all created temporary directories upon tear down.
    '''
    derived_from = [Test_Run]
}

req.Software_Requirement Compare_Stdout {
    description = '''
        The test asserter shall compare the actual value with the an expected
        value of STDOUT of the tool under test.
    '''
    derived_from = [Fail_on_Cmd_Output_Mismatch]
}

req.Software_Requirement Compare_Stderr {
    description = '''
        The test asserter shall compare the actual value with the an expected
        value of STDERR of the tool under test.
    '''
    derived_from = [Fail_on_Cmd_Output_Mismatch]
}

req.Software_Requirement Compare_Exit_Code {
    description = '''
        The test asserter shall compare the actual value with the an expected
        value of the exit code of the tool under test.
    '''
    derived_from = [Fail_on_Exit_Code_Mismatch]
}

req.Software_Requirement Compare_Output_Files {
    description = '''
        The test asserter shall compare every file that has been generated by the tool
        under test in the current working directory with files that represent the
        correponding expectation values.

        Notes:
        - Corresponding expectation values are files that have the same name as the
            generated file.
        - It is impossible to know where the tool under test generated files.
            Hence the requirement is limited to the current working directory.
    '''
    derived_from = [Fail_on_Output_File_Mismatch]
}

req.Software_Requirement Slashes {
    description = '''
    The test asserter shall treat double backward slashes as if they were forward
    slashes when comparing actual values with expected values of LOBSTER output files.
    '''
    derived_from = [Fail_on_Output_File_Mismatch]
}

req.Software_Requirement CWD_Placeholder {
    description = '''
    The tests asserter shall replace the placeholder "CURRENT_WORKING_DIRECTORY" with
    the path of the current working directory before comparing actual values with
    expected values of LOBSTER output files.
    '''
    derived_from = [Fail_on_Output_File_Mismatch]
}

package cpptest_req
import req

req.System_Requirement Input_File {
    description = '''
      IF a list element given through the yaml config file option "files" is a file
    '''
}

req.System_Requirement_Aspect Input_File_Valid_Cpp_Test_File {
  description = '''
    AND IF the file content is valid,
    THEN the tool shall write the output in the LOBSTER interchange format to the file given in the out parameter
    AND exit with a zero return code.
  '''
}

req.System_Requirement_Aspect Input_File_Invalid_Cpp_Test_File {
  description = '''
    OTHERWISE IF the file content is invalid,
    THEN the tool shall write an error message to stderr
    AND exit with a non-zero return code.
  '''
}

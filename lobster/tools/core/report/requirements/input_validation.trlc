package core_report_req
import req
import UseCases

req.System_Requirement Invalid_JSON_File {
  description = '''
    IF an input file given in the configuration is not valid JSON,
    THEN the tool shall raise an error of type LOBSTER_Error
    AND shall exit with a non-zero return code
    AND shall report the name of that input file, together with the line and column
    at which the JSON syntax error was found.
  '''
  derived_from = [UseCases.Failure_On_Invalid_Input]
}

req.System_Requirement Invalid_JSON_Not_Dict {
  description = '''
    IF a JSON input file does not contain a dictionary at the top level,
    THEN the tool shall exit with a non-zero return code.
  '''
  derived_from = [UseCases.Failure_On_Invalid_Input]
}

req.System_Requirement Invalid_Schema {
  description = '''
    IF a lobster input file declares a schema other than "lobster-req-trace",
    "lobster-imp-trace", or "lobster-act-trace",
    THEN the tool shall report "unknown schema kind <schema>"
    AND shall exit with a non-zero return code.
  '''
  derived_from = [UseCases.Failure_On_Invalid_Input]
}

req.System_Requirement Invalid_Schema_Version {
  description = '''
    IF a lobster input file declares "lobster-req-trace" with a version other than 3
    or 4, or declares "lobster-imp-trace" or "lobster-act-trace" with a version other
    than 3,
    THEN the tool shall report "version <X> for schema <Y> is not supported"
    AND shall exit with a non-zero return code.
  '''
  derived_from = [UseCases.Failure_On_Invalid_Input]
}

req.System_Requirement Missing_Schema_Key {
  description = '''
    IF the input .lobster file is missing a schema key,
    THEN the tool shall exit with a non-zero return code.
  '''
  derived_from = [UseCases.Failure_On_Invalid_Input]
}

req.System_Requirement Missing_Version_Key {
  description = '''
    IF the input .lobster file is missing a version key,
    THEN the tool shall exit with a non-zero return code.
  '''
  derived_from = [UseCases.Failure_On_Invalid_Input]
}

req.System_Requirement Malformed_Location_Data_Error_Dump {
  // This requirement does not describe the error message in detail, because
  // the current implementation just dumps the location data as a raw Python dict repr,
  // which is a debug artifact rather than a designed user-facing message.
  // TODO: Consider adding a friendlier message to the requirement.

  description = '''
    IF an item's location data is not an object, is missing the required "kind"
    field, or specifies an unrecognized "kind",
    THEN the tool shall print at least "LOBSTER Error"
    AND shall exit with a non-zero return code.
  '''
  derived_from = [UseCases.Failure_On_Invalid_Input]
}

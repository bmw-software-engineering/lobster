package codebeamer_req
import req
import UseCases

req.System_Requirement No_Source_Parameter {
  description = '''
    IF the configuration parameter "import_query" and "import_tagged" are both not
    provided (either missing in the configuration file or set to an empty string),
    THEN the tool shall display an error message and exit with a non-zero return code.
  '''
  derived_from = [
    UseCases.Failure_On_Invalid_Input,
  ]
}

req.System_Requirement Config_File_Path_Error {
  description = '''
    IF the configuration file cannot be opened,
    THEN the tool shall print an error message to STDERR
    AND exit with return code 1.
  '''
  derived_from = [
    UseCases.Failure_On_Invalid_Input,
  ]
}

req.System_Requirement Default_Config_File_Used {
  description = '''
    IF no configuration file path is specified with the "--config" command-line
    parameter,
    THEN the tool shall use "codebeamer-config.yaml" in the current working directory
    as the configuration file.
  '''
  derived_from = [
    UseCases.Tool_Usability,
  ]
}

req.System_Requirement Unsupported_Config_Keys_Rejected {
  description = '''
    IF the configuration file contains an unsupported key,
    THEN the tool shall print an error message to STDERR identifying the unsupported key
    AND exit with return code 1.
  '''
  derived_from = [
    UseCases.Failure_On_Invalid_Input,
  ]
}

req.System_Requirement Empty_Query_Message {
  description = '''
    IF the codebeamer server returns an empty list as (a result of the query),
    THEN the tool shall display a message to the user.
  '''
  derived_from = [
    UseCases.Tool_Usability,
  ]
}

req.Software_Requirement Get_Query_Zero_Items_Message {
  description = '''
    The function "get_query" shall print a message to the user IF the query returns zero items.
  '''
  derived_from = [Empty_Query_Message]
}

req.System_Requirement Retry_On_Specific_HTTPS_Status_Codes {
  description = '''
    IF the configuration parameter "retry_error_codes" is defined
    AND is a non-empty list
    AND the actual HTTPS return code from the last request is in the list specified by
    the configuration parameter "retry_error_codes"
    AND the configuration parameter "num_request_retry" is greater than 0 or not defined,
    THEN the tool shall retry the request up to a maximum of "num_request_retry" times
    (default is 5 if not set).
  '''
  derived_from = [
    UseCases.Tool_Usability,
  ]
}

req.System_Requirement References_Field_Support {
  description = '''
    IF an element given through the configuration option "refs" is a list of codebeamer
    field names,
    THEN the tool shall extract the corresponding references from the given codebeamer
    item fields,
    either from a same-named top-level field on the item or, if that field is absent or empty,
    from a "customFields" entry with a matching name,
    AND add a Tracing_Tag entry to the LOBSTER item for each referenced item ID.

    Note: Here the term "item" refers to a codebeamer JSON item as returned by the server
    through its API.
  '''
  derived_from = [
    UseCases.List_Ok_Items,
    UseCases.List_Not_Ok_Items,
    UseCases.Item_Coverage,
  ]
}

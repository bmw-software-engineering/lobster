package example

Requirement req_implication
{
   text = "provide a utility function for logical implication"
   trace_cb = 12345
}

Requirement req_xor
{
   text = "provide a utility function for logical exclusive or"
   trace_cb = 12345
}

Requirement req_nand
{
   text = "provide a utility function for logical negated and"
   trace_cb = 12345
}

Requirement req_nor
{
   text = "provide a utility function for logical negated or"
   trace_cb = 12345
}

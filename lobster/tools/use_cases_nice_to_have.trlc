package UC_Nice_to_have
import req

req.UseCase race_codebeamer_cpptest_Nice_to_have_1 {
    description = '''
        As a requirement manager I want traceability report to highlight the missing traces and good traces in different colour.
    '''
}

req.UseCase race_codebeamer_cpptest_Nice_to_have_2 {
    description = '''
        As a requirement manager I want traceability report to be generated in English Language.
    '''
}

req.UseCase race_codebeamer_cpptest_Nice_to_have_3 {
    description = '''
        As a requirement manager I want traceability report to have hyperlinks to the sections of the html report.
    '''
}

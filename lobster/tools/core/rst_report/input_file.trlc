package rst_req
import req

req.System_Requirement Missing_Lobster_File {
    description = '''
      IF the input .lobster file does not exist or is missing,
      THEN the tool shall exit with a non-zero return code (2)
      AND shall print an error message to STDERR indicating that the specified file is not a valid file.
    '''
}

req.System_Requirement Valid_Lobster_File {
    description = '''
      IF a valid .lobster file is provided as input,
      THEN the tool shall execute successfully with a zero return code (0)
      AND shall write a valid RST report to the specified output file (single-page mode).
    '''
}

req.System_Requirement Valid_Lobster_File_Multi_Page {
    description = '''
      IF a valid .lobster file is provided as input together with the --out-dir option,
      THEN the tool shall execute successfully with a zero return code (0)
      AND shall write a set of RST files (index.rst and one file per tracing level)
      to the specified output directory.
    '''
}

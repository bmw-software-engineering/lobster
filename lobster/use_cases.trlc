/* LOBSTER - Lightweight Open BMW Software Traceability Evidence Report
 * Copyright (C) 2025-2026 Bayerische Motoren Werke Aktiengesellschaft (BMW AG)
 *
 * This program is free software: you can redistribute it and/or modify
 * it under the terms of the GNU Affero General Public License as
 * published by the Free Software Foundation, either version 3 of the
 * License, or (at your option) any later version.
 *
 * This program is distributed in the hope that it will be useful, but
 * WITHOUT ANY WARRANTY; without even the implied warranty of
 * MERCHANTABILITY or FITNESS FOR A PARTICULAR PURPOSE. See the GNU
 * Affero General Public License for more details.
 *
 * You should have received a copy of the GNU Affero General Public
 * License along with this program. If not, see
 * <https://www.gnu.org/licenses/>.
 */
package UseCases
import req

/**
 * The role "traceability manager" is meant to be a placeholder role for a requirements
 * manager, test manager or quality manager. LOBSTER is a generic traceability tool, so
 * it can be used in many different contexts.
 *
 * The role "user" refers to any individual who interacts with any LOBSTER tool,
 * like a CI administrator who integrates LOBSTER into their continuous integration
 * pipeline, or a reader of the HTML report.
 */

section "Generic" {
    /**
     * This section contains use cases which are agnostic of the type of the actually
     * traced data. They do not know if the user wants to measure the coverage of
     * requirements, tests, source code functions, bug issues, architecture elements,
     * or any other type of traceable artifact.
     */

    req.UseCase List_Ok_Items {
        description = '''
            As a traceability manager I want the traceability report to list items that
            fulfill the tracing policy, and how they do so,
            so that I can decide whether to release my product.

            Example:
            If the tracing policy is: Tests --(trace to)--> Requirements,
            then the report shall list all tests that link to at least one requirement,
            and the report shall list all linked requirements per test.

            The use case applies to the reverse direction as well.
        '''
        affected_tools = [
            // extractor tools
            req.Tools.lobster_codebeamer,
            req.Tools.lobster_trlc,
            req.Tools.lobster_json,
            req.Tools.lobster_cpptest,
            req.Tools.lobster_pkg,

            // generator/rendering tools:
            req.Tools.lobster_report,
            req.Tools.lobster_ci_report,
            req.Tools.lobster_html_report,
            req.Tools.lobster_rst_report,
        ]
    }

    req.UseCase List_Not_Ok_Items {
        description = '''
            As a traceability manager I want the traceability report to list items that
            are not covered by other items, where coverage rules are specified by the
            tracing policy,
            so that I can identify gaps in the coverage.

            Example:
            If the tracing policy is: Tests --(trace to)--> Requirements,
            then the report shall list all tests that do not link to any requirement.

            The use case applies to the reverse direction as well.
        '''
        affected_tools = [
            // extractor tools
            req.Tools.lobster_codebeamer,
            req.Tools.lobster_trlc,
            req.Tools.lobster_json,
            req.Tools.lobster_cpptest,
            req.Tools.lobster_pkg,

            // generator/rendering tools:
            req.Tools.lobster_report,
            req.Tools.lobster_ci_report,
            req.Tools.lobster_html_report,
            req.Tools.lobster_rst_report,
        ]
    }

    req.UseCase Item_Coverage {
        description = '''
            As a traceability manager I want the traceability report to show the fraction
            of the number of items in one level (of the tracing policy)
            which fulfill the tracing policy,
            divided by the total number of items in that level (of the tracing policy).
            The fraction shall be shown as percentage.

            Example:
            If the tracing policy is: Tests --(trace to)--> Requirements,
            then the report shall show the fraction of requirements which are covered by at
            least one test, divided by the total number of requirements.
        '''
        affected_tools = [
            // extractor tools
            req.Tools.lobster_codebeamer,
            req.Tools.lobster_trlc,
            req.Tools.lobster_json,
            req.Tools.lobster_cpptest,
            req.Tools.lobster_pkg,

            // generator/rendering tools:
            req.Tools.lobster_report,
            req.Tools.lobster_ci_report,
            req.Tools.lobster_html_report,
            req.Tools.lobster_rst_report,
        ]
    }
}

req.UseCase List_Requirements_to_Tests {
    deprecated_by = List_Ok_Items
    description = '''
        As a requirements manager I want the traceability report to show the list of
        requirements which are covered by tests.
    '''
    affected_tools = [
        // shall extract requirements:
        req.Tools.lobster_codebeamer,
        req.Tools.lobster_trlc,

        // shall extract test cases:
        req.Tools.lobster_json,
        req.Tools.lobster_cpptest,
        req.Tools.lobster_pkg,

        // shall generate reports:
        req.Tools.lobster_report,
        req.Tools.lobster_html_report,
        req.Tools.lobster_rst_report
    ]
}

req.UseCase List_Requirements_without_Tests {
    deprecated_by = List_Not_Ok_Items
    description = '''
        As a requirements manager I want the traceability report to show the list of
        requirements which are not covered by tests.
    '''
    affected_tools = [
        // shall extract requirements:
        req.Tools.lobster_codebeamer,
        req.Tools.lobster_trlc,

        // shall extract test cases:
        req.Tools.lobster_json,
        req.Tools.lobster_cpptest,
        req.Tools.lobster_pkg,

        // shall generate reports:
        req.Tools.lobster_report,
        req.Tools.lobster_html_report,
        req.Tools.lobster_rst_report
    ]
}

req.UseCase List_Tests_to_Requirements {
    deprecated_by = List_Ok_Items
    description = '''
        As a requirements manager I want the traceability report to show the list of
        tests covering requirements.
    '''
    affected_tools = [
        // shall extract requirements:
        req.Tools.lobster_codebeamer,
        req.Tools.lobster_trlc,

        // shall extract test cases:
        req.Tools.lobster_json,
        req.Tools.lobster_cpptest,
        req.Tools.lobster_pkg,

        // shall generate reports:
        req.Tools.lobster_report,
        req.Tools.lobster_html_report,
        req.Tools.lobster_rst_report
    ]
}

req.UseCase List_Tests_without_Requirements {
    deprecated_by = List_Not_Ok_Items
    description = '''
        As a requirements manager I want the traceability report to show the list of
        tests which are not covering any requirement.
    '''
    affected_tools = [
        // shall extract requirements:
        req.Tools.lobster_codebeamer,
        req.Tools.lobster_trlc,

        // shall extract test cases:
        req.Tools.lobster_json,
        req.Tools.lobster_cpptest,
        req.Tools.lobster_pkg,

        // shall generate reports:
        req.Tools.lobster_report,
        req.Tools.lobster_html_report,
        req.Tools.lobster_rst_report
    ]
}

req.UseCase Show_Tracing_Policy {
    description = '''
        As a requirements manager I want the traceability report to show the tracing
        policy used to generate the report.
    '''
    affected_tools = [
        req.Tools.lobster_report,
        req.Tools.lobster_html_report,
        req.Tools.lobster_rst_report
    ]
}

req.UseCase Show_codebeamer_links {
    description = '''
        As a requirements manager I want the traceability report to mention the
        codebeamer link to each requirement in codebeamer.
    '''
    affected_tools = [
        // shall extract the source URL
        req.Tools.lobster_codebeamer,

        // shall propagate the source URL to the output
        req.Tools.lobster_report,

        // shall render the source URL
        req.Tools.lobster_html_report,
        req.Tools.lobster_rst_report
    ]
}

req.UseCase Item_GitHub_Source {
    description = '''
        As a requirements manager
        I want the traceability report
        to mention the GitHub location of each item which comes from a file inside a git
        repository (hosted on my company's GitHub Enterprise server),
        so that I can
        - map the traceability report to a commit SHA, and
        - easily navigate to the corresponding location.

        The location shall include:
        - the full URL including the git commit SHA,
        - and the line number (if applicable).

        Note:
        - The assumption is that, the repository will be checked out locally by the user
          or CI system, and the URL to the remote repository will be given as input to
          the LOBSTER tool suite. That is, the tool suite does not have to detect the
          commit SHA on its own.
        - The line number is optional, because otherwise it is impossible to represent
          files as a whole by a LOBSTER item.
    '''
    affected_tools = [
        // shall convert file references to GitHub references
        req.Tools.lobster_online_report,

        // shall render the references
        req.Tools.lobster_html_report,
        req.Tools.lobster_rst_report
    ]
}

req.UseCase HTML_Output {
    description = '''
        As a requirements manager I want to have the traceability report as a single
        stand-alone HTML file.

        Note: This simplifies any archiving process, because no additional CSS files or
        alike are required.
    '''
    affected_tools = [
        req.Tools.lobster_html_report
    ]
}

req.UseCase RST_Output {
    description = '''
        As a requirements manager I want the traceability report to be generated as
        reStructuredText (RST) for inclusion in a Sphinx documentation project,
        with the option to produce either a single combined document or a set of
        individual pages, one per tracing level.
    '''
    affected_tools = [
        req.Tools.lobster_rst_report
    ]
}

req.UseCase List_Findings {
    description = '''
        As a requirements manager I want the traceability report
        to show a list with all findings
        where the tracing policy is violated.
    '''
    affected_tools = [
        req.Tools.lobster_html_report,
        req.Tools.lobster_rst_report
    ]
}

req.UseCase CI_Build_Gate {
    description = '''
        As a CI administrator I want a tool that inspects a generated traceability
        report and exits with a non-zero return code whenever at least one item
        is not fully traced,
        AND printing each problem in a compiler-message style,
        CI pipeline can catch broken traceability automatically.
    '''
    affected_tools = [
        req.Tools.lobster_ci_report
    ]
}

req.UseCase Failure_On_Invalid_Input {
    description = '''
        As a CI administrator
        I want that the tool exits with a non-zero return code whenever it encounters
        invalid input
        so that the CI pipeline can catch invalid input automatically.
    '''
    affected_tools = [
        req.Tools.lobster_codebeamer,
        req.Tools.lobster_cpptest,
        req.Tools.lobster_report,
        req.Tools.lobster_trlc,
        req.Tools.lobster_json,
        req.Tools.lobster_pkg,
        req.Tools.lobster_online_report,
        req.Tools.lobster_html_report,
        req.Tools.lobster_rst_report,
        req.Tools.lobster_ci_report,
    ]
}

req.UseCase Bazel_Wrapped_Tool_Execution {
    description = '''
        As a CI administrator I want to invoke LOBSTER tools through Bazel commands
        (e.g. "bazel run //:lobster-ci-report -- <FILE>") instead of calling the
        underlying Python scripts directly, and I want a relative path typed on the
        command line to be resolved against the directory from which I invoked Bazel,
        even though Bazel itself executes the tool from a different working directory.
    '''
    affected_tools = [
        req.Tools.lobster_ci_report
    ]
}

req.UseCase Tool_Usability {
    description = '''
        As a user of LOBSTER I want to have a good usability and standard
        command-line ergonomics, like built-in help or automatic creation of output
        destinations,
        so that using the tools is intuitive and seamless in scripts and interactive
        use.
    '''
    affected_tools = [
        // extractor tools
        req.Tools.lobster_codebeamer,
        req.Tools.lobster_trlc,
        req.Tools.lobster_json,
        req.Tools.lobster_cpptest,
        req.Tools.lobster_pkg,

        // generator/rendering tools:
        req.Tools.lobster_report,
        req.Tools.lobster_ci_report,
        req.Tools.lobster_html_report,
        req.Tools.lobster_rst_report,
        req.Tools.lobster_online_report,
    ]
}

req.UseCase Codebeamer_Baseline_Query {
        description = '''
        As a user of lobster-codebeamer
        I want to fetch items from a codebeamer baseline
        so that I can create a traceability report for a baseline.
    '''
    affected_tools = [
        req.Tools.lobster_codebeamer,
    ]
}

req.UseCase GTest_Spec_From_Test_Name {
    description = '''
        As a test engineer I want lobster-gtest to derive the Given, When and
        Then specification of a test from its name, so that tests following a
        naming convention do not need a RecordProperty call for each part.
    '''
    affected_tools = [
        req.Tools.lobster_gtest,
    ]
}

req.UseCase Trace_Tests_From_JUnit_Reports {
    description = '''
        As a test engineer I want to trace the test cases of every test framework
        that writes JUnit XML reports, for example GoogleTest or pytest, to
        requirements with one tool, so that a test suite which mixes such
        frameworks is traced without sorting the reports by framework.
    '''
    affected_tools = [
        req.Tools.lobster_junit,
        req.Tools.lobster_gtest,
    ]
}

req.UseCase CI_Report_Coverage_Summary {
    description = '''
        As a requirements manager I want to see the per-level traceability
        coverage percentage printed directly to the console when checking a
        LOBSTER report, without having to generate or open an HTML report.
    '''
    affected_tools = [
        req.Tools.lobster_ci_report,
    ]
}

section "Nice to have" {
    /* Use cases in this section are nice to have, but are probably not relevant for a tool qualification in the sense of ISO 26262.
       As always, it is important to qualify a tool in the context of the project and company which uses the tool.
       LOBSTER is an open source project and the context is not known.
       There may be circumstances where the below use cases are essential for a project.
     */
    req.UseCase Colored_Findings {
        description = '''
            As a requirements manager I want the traceability report
            to highlight the missing traces and detected traces in different color.
        '''
        affected_tools = [
            req.Tools.lobster_html_report,
            req.Tools.lobster_rst_report
        ]
    }

    req.UseCase English_Language {
        description = '''
            As a requirements manager I want the traceability report
            to be generated in English language.
        '''
        affected_tools = [
            req.Tools.lobster_html_report,
            req.Tools.lobster_rst_report
        ]
    }

    req.UseCase PKG_Misplaced_Trace_Warning {
        description = '''
            As a requirements manager I want lobster-pkg to print a warning
            for lobster-traces in <DESCRIPTION> and <VALUE> nodes
            which are not extracted (due to wrong XML node or path properties).
        '''
        affected_tools = [
            req.Tools.lobster_pkg,
        ]
    }
}

package core_report_req
import req

req.System_Requirement_Aspect Status_Justified_Global {
  description = '''    
    IF the "just_global" list of the [[item]] contains at least one value,
    THEN the tool shall set the tracing status to "JUSTIFIED" of that [[Item]].
  '''
}

req.System_Requirement_Aspect Status_Justified_Up {
  description = '''    
    OTHERWISE
    IF the "just_up" list of the [[item]] contains at least one value
    AND there is at least one level in "trace to" in the tracing policy for the level of the item,
    THEN the tool shall set the tracing status to "JUSTIFIED" of that [[Item]].
  '''
}

req.System_Requirement_Aspect Status_Justified_Down {
  description = '''
    OTHERWISE
    IF the "just_down" list of the [[item]] contains at least one value
    AND the level of the item is mentioned in at least one "trace to" entry of any other level,
    THEN the tool shall set the tracing status to "JUSTIFIED" of that [[Item]].
  '''
}

req.System_Requirement_Aspect Status_Missing {
  description = '''    
    OTHERWISE, IF an [[Item]] has no references to an [[Item]] from a level mentioned in trace to,
    THEN the tool shall set the tracing status to "MISSING" of that [[Item]] and write "missing up reference" into the message section according to the schema.
  '''
}

req.System_Requirement_Aspect Status_Ok {
  description = '''    
    OTHERWISE, IF an [[Item]] has references to an [[Item]] from a level mentioned in trace to,
    THEN the tool shall set the tracing status to "OK" of that [[Item]]
  '''
}

req.System_Requirement_Aspect Invalid_Version {
  description = '''
    IF a lobster input file contains a schema with an unsupported version number,
    THEN the tool shall:
    - Report "version <X> for schema <Y> is not supported"
    - Exit with a non-zero return code
  '''
}

req.System_Requirement_Aspect Lobster_Exception_Dump_Invalid_Input {
  description = '''
    IF the tool detects an invalid input file
    AND raises a LOBSTER_Exception,
    THEN the tool shall invoke the exception's dump() method
    to display the error details in the standard output
    AND exit with a non-zero return code.
  '''
}

req.System_Requirement_Aspect Multiple_Traces_Support {
  description = '''
    IF the [[Item]] has multiple references across file,
    THEN the tool shall correctly consolidate the traces and report the tracing relationships.
  '''
}

req.System_Requirement_Aspect Linear_Policy_Support {
  description = '''
    IF the tracing policy is a linear tracibility where each level traces to exactly one other level,
    forming a linear chain of traceability,
    THEN the tool support linear tracing policies.
  '''
}

req.System_Requirement_Aspect Complex_Multi_Level_Policy_Support {
  description = '''
    IF the tracing policy is complex with multiple interconnected levels,
    where traceability can exist between multiple levels,
    THEN tool shall support complex tracing policies.
  '''
}

req.System_Requirement_Aspect Input_Files_Policy_Based_Processing {
  description = '''
    IF multiple input files are available in the workspace,
    THEN the tool shall only process the input files specified in the tracing policy configuration
    AND shall ignore any additional lobster files not referenced in the policy.
  '''
}

req.System_Requirement_Aspect Multi_Level_Source_Files {
  description = '''
    IF the tracing policy defines multiple levels with multiple source files for each level,
    THEN the tool shall correctly process and consolidate all source files and generate lobster report.
  '''
}

req.System_Requirement_Aspect Message_Trace_Coverage {
  description = '''
    IF an item contains a "message" and traces to another item,
    THEN the traced item shall have 100% coverage,
    AND the item with the message shall have 0% coverage.
  '''
}

req.System_Requirement_Aspect Item_Data_Isolation {
  description = '''
    IF the tool processes multiple items with their respective data and information,
    THEN the tool shall ensure that data do not get mixed between different items,
    AND each [[item]] shall maintain its own distinct data,
  '''
}

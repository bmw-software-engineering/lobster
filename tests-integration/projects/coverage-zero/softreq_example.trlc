package softreq_coverage_example
import coverage_example
import sysreq_coverage_example

coverage_example.Software_Requirement requirement_3a
{
   text = '''Requirement 3a'''
}

coverage_example.Software_Requirement requirement_3b
{
   text = '''Requirement 3b'''
}

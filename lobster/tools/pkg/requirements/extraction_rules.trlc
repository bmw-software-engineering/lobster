package pkg_req
import req
import UseCases

req.System_Requirement Pkg_Invalid_Xml {
    description =
    '''
        IF an input file cannot be parsed as XML,
        THEN the tool SHALL print an error message identifying the file and the parse
        error to STDOUT
        AND SHALL exit with a non-zero return code.
    '''
    derived_from = [
        UseCases.Failure_On_Invalid_Input,
    ]
}

req.System_Requirement Pkg_No_Input_Files {
    description =
    '''
        IF no input files or directories are given on the command line,
        THEN the tool SHALL print an error message stating that no input files were
        found to process
        AND SHALL exit with a non-zero return code.
    '''
    derived_from = [
        UseCases.Failure_On_Invalid_Input,
    ]
}

req.System_Requirement Input_Not_File_Not_Directory {
    description =
    '''
        IF a command line argument is neither an existing file nor an existing
        directory,
        THEN the tool SHALL print an error message identifying the offending argument
        to STDERR
        AND SHALL exit with a non-zero return code.
    '''
    derived_from = [
        UseCases.Failure_On_Invalid_Input,
    ]
}

req.System_Requirement Pkg_Output_Directory_Created {
    description =
    '''
        IF the directory of the given output file path does not exist,
        THEN the tool SHALL create it, including any missing parent directories,
        before writing the output file.
    '''
    derived_from = [
        UseCases.Tool_Usability,
    ]
}

req.System_Requirement Pkg_File_Item {
    description =
    '''
        The tool SHALL create a LOBSTER output item of type "Activity" for each input file
        IF the file represents a test case, identified by having an <INFORMATION> node
        containing a <TAGS> node with a <TAG> child node whose text is "TESTCASE"
        (case-insensitive)
        OR IF a lobster-trace is given in an ANALYSIS block
        (details see [[Trace_in_Analysis_Node]]).

        The following requirements describe how to fill the "refs" attribute of these
        items.

        Note: If no requirements is fulfilled, which describes how to fill the "refs" attribute,
        then the item SHALL be created with an empty "refs" attribute.
    '''
    derived_from = [
        UseCases.List_Requirements_to_Tests,
        UseCases.List_Requirements_without_Tests,
        UseCases.List_Tests_to_Requirements,
        UseCases.List_Tests_without_Requirements,
        UseCases.Item_Coverage
    ]
}

req.System_Requirement Trace_in_Test_Step_Node {
    description = '''
        Note: Pay attention to the difference between TESTSTEP and TESTSTEPS!

        The tool SHALL extract all tags (marked by "lobster-trace") from <VALUE> nodes
        from the specified input files
        WHERE all of the following conditions apply:
        - The file SHALL be a test case, identified by having an <INFORMATION> node
        containing a <TAGS> node with a <TAG> child node whose text is "TESTCASE"
        (case-insensitive).
        - The <TESTSTEPS> node is of type "testCase".
        - The <TESTSTEP> node is the first child node of a <TESTSTEPS> node.
        - The <TESTSTEP> node is named "TsBlock".
        - The <VALUE> node is nested inside a <TESTSTEP> node.
        - The <VALUE> node contains one or more substrings in the format
        "lobster-trace:<REQUIREMENT_ID>"
    '''
    derived_from = [
        UseCases.List_Requirements_to_Tests,
        UseCases.List_Requirements_without_Tests,
        UseCases.List_Tests_to_Requirements,
        UseCases.List_Tests_without_Requirements,
        UseCases.Item_Coverage
    ]
}

req.System_Requirement Trace_in_Analysis_Node {
    description = '''
        The tool SHALL extract all tags (marked by "lobster-trace") from <DESCRIPTION> nodes
        from the specified input files
        WHERE all of the following conditions apply:
        - The <ANALYSISITEM> node is a **direct** child node of a <TRACE-ANALYSIS> node.
        - The <ANALYSISITEM> node is of type "episode".
        - The <DESCRIPTION> node is a **direct** child node of an <ANALYSISITEM> node.
        - The <DESCRIPTION> node contains the substring in the format
        "lobster-trace:<REQUIREMENT_ID>"
    '''
    derived_from = [
        UseCases.List_Requirements_to_Tests,
        UseCases.List_Requirements_without_Tests,
        UseCases.List_Tests_to_Requirements,
        UseCases.List_Tests_without_Requirements,
        UseCases.Item_Coverage
    ]
}

req.System_Requirement Misplaced_Value_Node_Trace_Error {
    description =
    '''
        IF a "lobster-trace" tag is found in a <VALUE> node which does not satisfy the
        nesting conditions of [[Trace_in_Test_Step_Node]],
        THEN the tool SHALL print an error message identifying the file and the line
        number(s) of the misplaced tag(s)
        AND SHALL exit with a non-zero return code.
    '''
    derived_from = [
        UseCases.PKG_Misplaced_Trace_Warning,
        UseCases.Failure_On_Invalid_Input,
    ]
}

req.System_Requirement Misplaced_Description_Node_Trace_Warning {
    description =
    '''
        IF a "lobster-trace" tag is found in a <DESCRIPTION> node which does not satisfy
        the nesting conditions of [[Trace_in_Analysis_Node]],
        THEN the tool SHALL print a warning message to STDOUT identifying the file and
        the misplaced tag
        AND SHALL continue processing the remaining input.

        Note: This requirement does not influence the tool return code.
    '''
    derived_from = [
        UseCases.PKG_Misplaced_Trace_Warning,
        UseCases.Failure_On_Invalid_Input,
    ]
}

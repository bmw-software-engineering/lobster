package trlc_req
import req
import UseCases

req.System_Requirement Config_Option_Mandatory {
  description = '''
    IF the command line option "--config" is not given,
    THEN the tool SHALL print a usage error to STDERR
    AND SHALL exit with a non-zero code.
  '''
  derived_from = [
    UseCases.Failure_On_Invalid_Input,
  ]
}

req.System_Requirement Config_File_Not_Found {
  description = '''
    IF the file given through the command line option "--config" does not exist,
    THEN the tool SHALL print an error message stating that the file was not found
    to STDERR
    AND SHALL exit with a non-zero return code.
  '''
  derived_from = [
    UseCases.Failure_On_Invalid_Input,
  ]
}

req.System_Requirement Config_File_Invalid_Schema {
  description = '''
    IF the file given through the command line option "--config" does not conform to
    the expected schema (defined in the file "schema.yamale"),
    THEN the tool SHALL print an error message identifying the schema violation to
    STDERR
    AND SHALL exit with a non-zero return code.
  '''
  derived_from = [
    UseCases.Failure_On_Invalid_Input,
  ]
}

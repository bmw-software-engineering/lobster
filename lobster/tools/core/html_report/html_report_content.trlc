package html_req
import req

req.System_Requirement Meta_Tag_In_Html_Report {
    description = '''
      IF a HTML report is generated,
      THEN the file should contain meta tag,
      HAVING attributes "http-equiv" and "content".
    '''
}

req.System_Requirement HTML_Report_with_20k_records {
    description = '''
      IF a valid .lobster file containing approximate 20 thousand items is provided as input,
      THEN the tool shall execute successfully with a zero return code (0)
      AND shall write a valid HTML report to the specified output file.
    '''
}

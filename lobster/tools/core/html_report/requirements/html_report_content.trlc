package html_req
import req
import UseCases

req.System_Requirement HTML_Report_Uses_Valid_HTML_Syntax {
    description = '''
      The tool shall generate an HTML report that adheres to valid HTML syntax.
    '''
    derived_from = [UseCases.HTML_Output]
}

req.System_Requirement Meta_Tag_In_Html_Report {
    description = '''
      The HTML output file shall contain the meta tag
      with attributes "http-equiv" and "content".
    '''
    derived_from = [UseCases.HTML_Output]
}

req.System_Requirement Item_Data_Unique {
    description = '''
      The tool shall print all items from the input file into the HTML output file,
      including their carried data.
    '''
    derived_from = [UseCases.HTML_Output]
}

req.System_Requirement Tracing_Policy_Image {
    description = '''
      IF the tool "dot" is available, 
      THEN the tool shall include a visualization of the tracing policy
      in the HTML report.
    '''
    derived_from = [UseCases.Show_Tracing_Policy]
}

req.System_Requirement Only_Given_Input_File_Consumed {
    description = '''
      IF the tool is invoked with an explicit input ".lobster" file
      THEN the tool shall generate the HTML report from that file.
      OTHERWISE the tool shall use a default "report.lobster" input file name.
    '''
    derived_from = [UseCases.Tool_Usability]
}

req.System_Requirement Processing_Data_With_Justifications {
    description = '''
      IF the input data contains items with justifications,
      THEN the tool shall process the justifications correctly,
      AND shall display the content according to the justifications in the HTML report.
    '''
    derived_from = [UseCases.List_Findings]
}

req.System_Requirement HTML_Report_Lists_Lobster_Items {
    description = '''
      IF a LOBSTER report contains items,
      THEN the generated HTML file shall display those items and their associated
      traceability information.
    '''
    derived_from = [
      UseCases.List_Requirements_to_Tests,
      UseCases.List_Requirements_without_Tests,
      UseCases.List_Tests_to_Requirements,
      UseCases.List_Tests_without_Requirements
    ]
}

req.System_Requirement HTML_Report_Displays_Findings_Per_Item {
    description = '''
      IF an item in the LOBSTER report has one or more findings or tracing messages,
      THEN the generated HTML file shall display those findings for that item.
    '''
    derived_from = [UseCases.List_Findings]
}

req.System_Requirement HTML_Report_Displays_Coverage_Value {
    description = '''
      The generated HTML file shall display the coverage value for each level.
    '''
    derived_from = [UseCases.Item_Coverage]
}

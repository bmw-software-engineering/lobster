package json_req
import req

req.Software_Requirement Synthetic_Tag_Name {
  description = '''
    If the command line option --name-attribute is not given, then the tool shall create
    a synthetic tag name based on the path of the JSON input file and an item counter.

    Notes:
    - "Synthetic" means that, the name does not need to be related to the data.
    - The item counter does not need to be unique across files.
      But it shall be unique at least for each input file separately.
  '''
}

req.Software_Requirement Name_Attribute {
  description = '''
    If the command line option --name-attribute is given, then the tool shall
    - use the value of the command line argument as JSON key of the JSON item
    - and use that obtained value as LOBSTER item tag name.
  '''
}

package trlc_req

System_Requirement Output_File {
    description = '''
      If a output file is specified as command line argument, then the output must be written into that file.
      Otherwise, the output shall be written to 'trlc.lobster'.
    '''
}

package json_req
import req
import UseCases

req.System_Requirement Input_Not_File_Not_Directory {
    description = '''
      IF a list element given through the configuration file under "inputs" is not a file nor a directory,
      THEN the tool shall print an error message identifying the offending element to STDOUT,
      SHALL NOT write any output file,
      AND SHALL exit with a non-zero return code.
    '''
    derived_from = [
    UseCases.List_Ok_Items,
    UseCases.List_Not_Ok_Items,
    UseCases.Item_Coverage,
    ]
}

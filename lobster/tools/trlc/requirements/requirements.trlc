package trlc_req
import req
import UseCases

req.System_Requirement Output_File {
    description = '''
      If an output file is specified as a command line argument, then the output SHALL
      be written to that file. Otherwise, the output SHALL be written to
      'trlc.lobster'.

      Output content:
      The tool SHALL populate each generated LOBSTER item's tag, location, and
      description fields using the data from the single corresponding TRLC record
      object.
    '''
    derived_from = [
      UseCases.List_Ok_Items,
      UseCases.List_Not_Ok_Items,
      UseCases.Item_Coverage,
    ]
}

req.System_Requirement Trlc_Record_Object_To_Lobster_Item {
    description = '''
      IF the consumed input contains a TRLC record object whose type matches a
      configured conversion rule,
      THEN the tool SHALL generate exactly one LOBSTER item for that record object.
      The generated item's tag, source location, and description SHALL be derived
      from that same record object.
    '''
    derived_from = [
      UseCases.List_Ok_Items,
      UseCases.List_Not_Ok_Items,
      UseCases.Item_Coverage,
    ]
}


req.System_Requirement Command_Line_Args_From_File {
    description = '''
      IF a command line argument is prefixed with "@",
      THEN the tool SHALL read the contents of the file named by the remainder of
      that argument, and SHALL include each of its contained arguments as if they
      had been given directly on the command line.
    '''
    derived_from = [
      UseCases.Tool_Usability,
    ]
}

req.Software_Requirement Args_From_File {
    /* FIXME: This is a software requirement for the MetaDataToolBase class,
       but currently our TRLC/LOBSTER tracing setup in the repository does not offer a
       way to manage shared requirements in "lobster/common".
     */
    description = '''
      The MetaDataToolBase class shall create the ArgumentParser instance with
      setting the parameter 'fromfile_prefix_chars' to '@'.
    '''
    derived_from = [Command_Line_Args_From_File]
}

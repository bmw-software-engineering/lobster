package cpptest_req
import req
import UseCases

req.System_Requirement Default_Files_Is_Current_Directory {
  description = '''
    IF the config option "files" is not given,
    THEN the tool SHALL use the current working directory as the sole input,
    applying the same directory-search rule as for an explicitly configured
    directory.
  '''
  derived_from = [
    UseCases.Tool_Usability,
  ]
}

req.System_Requirement Input_Directory_Traversal {
  description = '''
    IF a list element given through the config option "files" is a directory,
    THEN the tool SHALL recursively search that directory
    AND SHALL treat every file found with one of the extensions ".cpp", ".cc",
    ".c", ".h" as an additional input file, ignoring any other file found there.
  '''
  derived_from = [
    UseCases.Tool_Usability,
  ]
}

req.System_Requirement Explicit_File_Ignores_Extension {
  description = '''
    IF a list element given through the config option "files" is a file,
    THEN the tool SHALL process it as an input file, regardless of its file
    extension.
  '''
  derived_from = [
    UseCases.Tool_Usability,
  ]
}

req.System_Requirement Input_Not_File_Not_Directory {
  description = '''
    IF a list element given through the config option "files" is neither a file
    nor a directory,
    THEN the tool SHALL print an error message identifying the offending element
    to STDERR
    AND SHALL exit with a non-zero return code.
  '''
  derived_from = [
    UseCases.Failure_On_Invalid_Input,
  ]
}

req.System_Requirement No_Test_Files_Found {
  description = '''
    IF the resolved set of input files (after applying [[Input_Directory_Traversal]]
    and [[Explicit_File_Ignores_Extension]]) is empty,
    THEN the tool SHALL print an error message identifying the configured "files"
    option to STDERR
    AND SHALL exit with a non-zero return code.
  '''
  derived_from = [
    UseCases.Failure_On_Invalid_Input,
  ]
}

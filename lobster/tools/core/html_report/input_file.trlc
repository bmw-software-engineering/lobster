package html_req
import req
import UseCases

req.System_Requirement Missing_Lobster_File {
    description = '''
      IF the input .lobster file does not exist or is missing,
      THEN the tool shall exit with a non-zero return code (2)
      AND shall print an error message to STDERR indicating that the specified file is not a valid file.
    '''
    derived_from = [UseCases.Failure_On_Invalid_Input]
}

req.System_Requirement Valid_Lobster_File {
    description = '''
      IF a valid .lobster file is provided as input
      AND the command line argument "--out" is provided,
      THEN the tool shall write a valid HTML report to the specified output file.
    '''
    derived_from = [UseCases.HTML_Output]
}

req.System_Requirement Valid_Lobster_File_With_Md_Content {
    description = '''
      IF the conditions of [[Valid_Lobster_File]] are given
      AND the command line argument "--render-md" is provided,
      THEN the tool shall interpret the text property of every LOBSTER item as Markdown
      and render it accordingly as HTML in the generated report.
    '''
    derived_from = [
      UseCases.HTML_Output,
      UseCases.Tool_Usability,
    ]
}

req.System_Requirement HTML_Report_Displays_Custom_data {
    description = '''
      IF a valid .lobster file containing a "custom_data" field 
      THEN the tool shall extract these values from the file
      AND shall render them in the top-right corner of the generated HTML report.
    '''
    derived_from = [UseCases.HTML_Output]
}

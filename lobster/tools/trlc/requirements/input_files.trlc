package trlc_req
import req
import UseCases

req.System_Requirement Input_List_Of_Files {
    description = '''
      IF the list elements given through the config option "inputs" are files with
      extension rsl, trlc and trlc.md,
      THEN all files given in "inputs" parameter shall be consumed.
    '''
    derived_from = [
      UseCases.List_Ok_Items,
      UseCases.List_Not_Ok_Items,
      UseCases.Item_Coverage,
    ]
}

req.System_Requirement Command_Line_Positional_Inputs {
    description = '''
      IF one or more DIR or FILE positional command line arguments are given,
      THEN the tool SHALL process them as additional inputs,
      applying the same rules as for the config option "inputs".
    '''
    derived_from = [
      UseCases.Tool_Usability,
    ]
}

req.System_Requirement Input_Not_File_Not_Directory {
    description = '''
      IF an input element, given through "inputs", "inputs_from_file", or a
      positional command line argument, is neither a file nor a directory,
      THEN the tool SHALL terminate with a non-zero return code, without generating
      output.
    '''
    derived_from = [
      UseCases.Failure_On_Invalid_Input,
    ]
}

req.System_Requirement Inputs_From_File {
    description = '''
      IF the element given through the config option "inputs_from_file" is a file,
      THEN each line in that file shall be interpreted as a path AND shall be consumed.
    '''
    derived_from = [
      UseCases.Tool_Usability,
    ]
}

req.System_Requirement Input_list_Of_File_And_Inputs_From_File {
    description = '''
      IF both the config options [[Input_List_Of_Files]] AND [[Inputs_From_File]] are provided,
      THEN all files given in [[Input_List_Of_Files]] AND [[Inputs_From_File]] parameter shall be consumed.
    '''
    derived_from = [
      UseCases.Tool_Usability,
    ]
}

req.System_Requirement Input_Directory_Traversal {
    description = '''
      IF a list element given through the config option "inputs" is a directory,
      THEN the tool SHALL recursively search that directory
      AND SHALL treat every file found with a valid extension (".rsl", ".trlc", ".trlc.md")
      as an additional input file.
    '''
    derived_from = [
      UseCases.Tool_Usability,
    ]
}

req.System_Requirement Invalid_File_Extension {
    description = '''
      IF an input file, given through "inputs", "inputs_from_file", or a positional
      command line argument, does not have one of the valid extensions
      (".rsl", ".trlc", ".trlc.md"),
      THEN the tool SHALL print an error message identifying the file and the expected
      extensions to STDERR
      AND SHALL exit with a non-zero return code.
    '''
    derived_from = [
      UseCases.Failure_On_Invalid_Input,
    ]
}

req.System_Requirement Duplicate_Definition_Aborts_Processing {
    /* Note: this effectively tests that the TRLC API detects duplicate definitions.
     * TRLC should provide an appropriate test instead, and this test by LOBSTER should
     * only verify that lobster-trlc handles TRLC errors. */
    description = '''
      IF the consumed input files contain duplicate definitions of the same TRLC
      identifier,
      THEN the tool SHALL print the locations of the duplicate and the original
      definition to STDOUT,
      SHALL print "aborting due to TRLC error" to STDERR,
      AND SHALL exit with a non-zero return code, without generating output.
    '''
    derived_from = [
      UseCases.Failure_On_Invalid_Input,
    ]
}

req.System_Requirement No_Inputs_Produces_Zero_Items {
    description = '''
      IF the consumed input files contain zero TRLC record objects
      (for example because no ".trlc" files were given, only ".rsl" schema files),
      AND every configured conversion rule matches at least one TRLC record type,
      THEN the tool SHALL write zero items to the output
      AND SHALL exit with return code 0.

      Note: [[Orphan_Conversion_Rule_Error]] describes the behavior if at least one
      conversion rule does not match any TRLC record type.
    '''
    derived_from = [
      UseCases.List_Ok_Items,
      UseCases.List_Not_Ok_Items,
      UseCases.Item_Coverage
    ]
}

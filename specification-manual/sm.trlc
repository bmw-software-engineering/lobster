package SM

Versioning Version {
  major = 1
  minor = 9
}

GFDL_License License {
  invariant_sections = []
}

section "LOBSTER" {

  Requirements Lobster {
    requirements = '''The Lightweight Open BMW Software Traceability Evidence Report allows you to 
     demonstrate software traceability and requirements coverage, which is essential for
     meeting standards such as ISO 26262.'''   
  }

  
}

/***********************************************************************/

section "Tools" {

  Requirements Tools {
    bullets = [
      '''`lobster-python`: Extract requirements from Python3 code''',   
      '''`lobster-cpp`: Extract requirements from C/C++ code using a clang-tidy hack. ''', 
      '''`lobster-codebeamer`: Extrat requirements from codebeamer.''',
    ]  
  }
}

/***********************************************************************/

section "TRLC" {

  Information Trlc {
    information = '''Treat Requirements Like Code (TRLC). TRLC is a domain-specific language
     for writing (and linking) requirements with meta-data.'''

    bullets = [
      '''lobster-trlc: Extract requirements from trlc code.''',     
    ]
  }
}

/***********************************************************************/
   
section "Python Usage" {
      Requirements Python_File {
        requirements = '''This tool supports both Python code and PyUnit/unittest unit tests.'''
      }
        Static_Defination Simple_String_Value {
           information = '''For either code or tests you can embedd tracing tags like this:.'''
          }
        bnf = ''' def potato(self):
              # lobster-trace: something.example
             return "potato"
             '''
  }




/***********************************************************************/

section "C/C++ Usage" {

Requirements Cpp_File{
  requirements = '''This tool supports C/C++ code.'''
  }
  Static_Defination Cpp_String_Value {
           information = '''For this you can embedd tracing tags like this:'''
          }
          defination ='''#include <string>
                        class Potato {
                        public:
                         std::string potato() {
                         // lobster-trace: something.example
                        return "potato";
                           }
                        };'''         

  Static_Defination Cpp_justifications_Value{
      requirements = '''You can add justifications as well:'''
  }
       defination ='''#include <string>
                       class Potato {
                        public:
                         std::string potato() {
                        // lobster-exclude: Reason to justify the exlude
                      return "potato";
                     }
                   };'''


}

/***********************************************************************/

Requirements Codebeamer_File{
         requirements = '''lobster-codebeamer: Extrat requirements from codebeamer.'''
}

 Static_Defination Codebeamer_String_Value {
   information = '''There are two ways you can use this tool:'''

   bullets = [
    '''Download all requirements mentioned by another lobster trace (this way you do not get a completeness check) (using --import-tagged)'''
    '''Download all requirements generated by a saved codebeamer query (using --import-query)'''
   ]
 }

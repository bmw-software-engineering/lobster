package UseCases
import req

req.TestSpecification Default_Path_Warning_Test {
    description = '''
        The test shall verify that when no input files are specified, the tool
        shall generate an output file with zero LOBSTER items.
        
        Test steps:
        - Run the TRLC tool without specifying any input files
        - Verify that the tool generates an output file with zero items.
    '''
    verifies = [Default_Path_Choice]
}


req.TestSpecification Incorrect_data_Extraction_from_TRLC {
    description = '''
        The test shall verify that the extracted data is consistent with
        the input data according to the configuration.
        
        For example, the input may contain 5 items of type "Information" and 6 items of type "Requirement".
        The configuration specifies to extract only "Requirement" items.
        The test needs to verify that these 6 requirement items are consistent with the LOBSTER output.
    '''
    verifies = [Wrong_Extraction_from_TRLC]
}

req.TestSpecification TRLC_Config_File_Missing {
    description = '''
        The test shall verify that the lobster-trlc tool exits with a non-zero return code when the config file does not exist.
        Example: Verify that the lobster-trlc tool throws an error when a non-existent config file is provided.
    '''
    verifies = [Output_Despite_Missing_Config_File_TRLC]
}

req.TestSpecification TRLC_Config_File_Syntax_Error {
    description = '''
        The test shall verify that lobster-trlc tool exits with a non-zero return code when the config file contains a syntax error.
        Example: Verify that lobster-trlc throws an error when a config file with invalid TRLC is provided.
    '''
    verifies = [Output_Despite_Config_File_Error_TRLC]
}


req.TestSpecification TRLC_Config_File_Key_Error {
    description = '''
        The test shall verify that lobster-trlc tool exits with a non-zero return code when the config file is missing required keys.
    '''
    verifies = [Output_Despite_Config_File_Error_TRLC]
}

req.TestSpecification TRLC_Config_File_non_existent_conversion_rules {
    description = '''
        The test shall verify that lobster-trlc tool exits with a non-zero return code when the config file contains
        conversion rules for TRLC record types which do not exist in the RSL file.
    '''
    verifies = [Output_Despite_Config_File_Error_TRLC]
}

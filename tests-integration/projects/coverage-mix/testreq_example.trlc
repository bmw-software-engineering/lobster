package testreq_coverage_half_example
import coverage_half_example
import softreq_coverage_half_example

coverage_half_example.Test_Requirement requirement_f
{
   text = '''Requirement3'''
   derived_from = [softreq_coverage_half_example.requirement_d]
   just_up = "needed"
   just_down = "needed"
}

package softreq_example
import exampletwo
import sysreq_example

exampletwo.Software_Requirement req_implication
{
   text = '''
      Implement a function with the signature 
         int implication(int x, int y) 
      that computes the logical implication of its two integer arguments. 
      The function returns 1 (true) if the first argument is 0 
      or the second argument is non-zero, and 0 (false) otherwise.
      '''
   trace_trlc = [sysreq_example.lobster_example, sysreq_example.req_implication]
}

exampletwo.Software_Requirement req_xor
{
   text = '''
      Implement a function with the signature 
         int exclusive_or(int x, int y) 
      to compute the exclusive or (XOR) of its two integer arguments. 
      The function returns 1 when exactly one of the arguments is non-zero and 0 otherwise.
      '''
   trace_trlc = [sysreq_example.lobster_example, sysreq_example.req_xor]
}

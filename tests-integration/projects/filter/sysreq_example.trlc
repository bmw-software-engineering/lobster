package sysreq_example
import filter_example

filter_example.System_Requirement lobster_example
{
   text = '''
      Provide a demonstration of LOBSTER with system and software requirements in TRLC with a source filter in lobster.conf
      '''
}

filter_example.System_Requirement req_implication
{
   text = '''
      The example shall provide a logical implication operation between two integer inputs 
      to determine if the second integer is logically implied by the first. 
      '''
}

filter_example.System_Requirement req_xor
{
   text = '''
      The example shall provide an exclusive or (XOR) operation between two integer inputs 
      to evaluate scenarios where a decision is based on the condition that exactly one of two inputs must be true (non-zero).
      '''
}

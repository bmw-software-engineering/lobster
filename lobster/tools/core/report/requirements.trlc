package core_report_req
import req

req.System_Requirement Report_Input_Duplicate_Definition {
  description = '''
    If any of the source files given in the lobster configuration file contains a tag
    more than once, then the tool must exit with code 1.
  '''
}

req.Software_Requirement Dummy_Requirement_Unit_Test {
  description = '''
    This is not really a requirement. It will be used only to generate a minimal tracing report for each tool.
    It can be deleted as soon as all the tools get their real requirements.
  '''
}

req.Definition Item {
  description = '''
    An item is an entry in the data section according to the schema.
  '''
}

req.System_Requirement_Aspect Invalid_Trace_To {
  description = '''
    IF "trace to" is an invalid entry given in the configuration file according to the schema,
    THEN the tool shall exit with a non-zero return code and with an error message "lobster error: unknown item".
  '''
}

req.System_Requirement_Aspect Status_Justified_Global {
  description = '''    
    IF the "just_global" list of the [[item]] contains at least one value,
    THEN the tool shall set the tracing status to "JUSTIFIED" of that [[Item]].
  '''
}

req.System_Requirement_Aspect Status_Justified_Up {
  description = '''    
    OTHERWISE
    IF the "just_up" list of the [[item]] contains at least one value
    AND there is at least one level in "trace to" in the tracing policy for the level of the item,
    THEN the tool shall set the tracing status to "JUSTIFIED" of that [[Item]].
  '''
}

req.System_Requirement_Aspect Status_Justified_Down {
  description = '''
    OTHERWISE
    IF the "just_down" list of the [[item]] contains at least one value
    AND the level of the item is mentioned in at least one "trace to" entry of any other level,
    THEN the tool shall set the tracing status to "JUSTIFIED" of that [[Item]].
  '''
}

req.System_Requirement_Aspect Status_Missing {
  description = '''    
    OTHERWISE, IF an [[Item]] has no references to an [[Item]] from a level mentioned in trace to,
    THEN the tool shall set the tracing status to "MISSING" of that [[Item]] and write "missing up reference" into the message section according to the schema.
  '''
}

req.System_Requirement_Aspect Status_Ok {
  description = '''    
    OTHERWISE, IF an [[Item]] has references to an [[Item]] from a level mentioned in trace to,
    THEN the tool shall set the tracing status to "OK" of that [[Item]]
  '''
}

req.System_Requirement_Aspect Zero_Items_Coverage {
  description = '''
    IF a level defined in the tracing policy has zero items in the corresponding input file,
    THEN the tool shall set the coverage for that level to 0.0 in the generated report file.
  '''
}

req.System_Requirement_Aspect Invalid_JSON_File {
  description = '''
    IF an input file given in the configuration is not valid JSON,
    THEN the tool shall raise an error of type LOBSTER_Error
    AND shall exit with a non-zero return code
    AND shall report the error location and message.
  '''
}

req.System_Requirement_Aspect Invalid_JSON_Not_Dict {
  description = '''
    IF a JSON input file does not contain a dictionary at the top level,
    THEN the tool shall raise a Exception,
    AND the tool shall exit with a non-zero return code.
  '''
}

req.System_Requirement_Aspect Invalid_Schema {
  description = '''
    IF a lobster input file contains a schema that is not in the list of supported schemas,
    THEN the tool shall:
    - Report "unknown schema kind <schema>"
    - Exit with a non-zero return code
  '''
}

req.System_Requirement_Aspect Invalid_Version {
  description = '''
    IF a lobster input file contains a schema with an unsupported version number,
    THEN the tool shall:
    - Report "version <X> for schema <Y> is not supported"
    - Exit with a non-zero return code
  '''
}

req.System_Requirement_Aspect Missing_Schema_Key {
  description = '''
    IF the input .lobster file is missing a schema key,
    THEN the tool shall raise a LOBSTER_Exception,
    AND the tool shall exit with a non-zero return code.
  '''
}

req.System_Requirement_Aspect Missing_Version_Key {
  description = '''
    IF the input .lobster file is missing a version key,
    THEN the tool shall raise a LOBSTER_Exception,
    AND the tool shall exit with a non-zero return code.
  '''
}

req.System_Requirement_Aspect Lobster_Exception_Dump_Invalid_Input {
  description = '''
    IF the tool detects an invalid input file
    AND raises a LOBSTER_Exception,
    THEN the tool shall invoke the exception's dump() method
    to display the error details in the standard output
    AND exit with a non-zero return code.
  '''
}

req.System_Requirement_Aspect Unknown_Tracing_Target {
  description = '''
    IF a reference in a lobster file points to a tag that does not exist in the set of loaded items,
    THEN the tool shall report "unknown tracing target <tag>" and exit with non-zero return code.
  '''
}

req.System_Requirement_Aspect Tracing_Destination_Unversioned {
  description = '''
    IF a reference specifies a version but the destination tag is unversioned,
    THEN the tool shall report "tracing destination <tag> is unversioned" and exit with non-zero return code.
  '''
}

req.System_Requirement_Aspect Tracing_Destination_Version_Mismatch {
  description = '''
    IF a reference specifies a version and the destination tag has a different version,
    THEN the tool shall report "tracing destination <tag> has version <x> (expected <y>)" and exit with non-zero return code.
  '''
}

req.System_Requirement_Aspect File_Not_Found {
  description = '''
    IF a required input file for the tool does not exist or cannot be accessed,
    THEN the tool shall report "file not found <file_path>" and exit with a non-zero return code.
  '''
}

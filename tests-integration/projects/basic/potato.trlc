package example

Tagged_Requirement req_implication
{
   text = "provide a utility function for logical implication"
   trace_cb = [12345]
}

Tagged_Requirement req_xor
{
   text = "provide a utility function for logical exclusive or"
   trace_cb = [12345@5]
}

Tagged_Requirement req_nand
{
  text = "provide a utility function for logical negated and"
  extra_text = "potato"
  trace_cb = [12345@42]
}

Requirement req_nor
{
   text = "provide a utility function for logical negated or"
}

Requirement req_implies
{
  text = "provide a utility function for logical implication"
  just_up = "not needed"
  just_down = "also not needed"
}

Information potato
{
   text = "this is just here for fun"
}

Linked_Requirement req_important
{
  text = "this is important"
  trace_trlc = [req_nor, req_nand]
}

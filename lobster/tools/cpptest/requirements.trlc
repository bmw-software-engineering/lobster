package cpptest_req
import req

req.Software_Requirement Dummy_Requirement {
  description = '''
    This is not really a requirement. It will be used only to generate a minimal tracing report for each tool.
    It can be deleted as soon as all the tools get their real requirements.
  '''
}

req.Software_Requirement Dummy_Requirement_Unit_Test {
  description = '''
    This is not really a requirement. It will be used only to generate a minimal tracing report for each tool.
    It can be deleted as soon as all the tools get their real requirements.
  '''
}

req.System_Requirement_Aspect Valid_Flow {
  description = '''
    IF a valid YAML config file with required keys is provided,
    AND valid test files are present in the specified paths,
    THEN the tool shall parse the test files, extract test cases,
    generate lobster items, and write them to the configured output.
  '''
}
